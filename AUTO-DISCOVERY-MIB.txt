AUTO-DISCOVERY-MIB DEFINITIONS ::= BEGIN

IMPORTS
    MODULE-IDENTITY, OBJECT-TYPE, Integer32, IpAddress, Counter32, Gauge32, TimeTicks
        FROM SNMPv2-SMI
    DisplayString 
        FROM SNMPv2-TC
    MODULE-COMPLIANCE, OBJECT-GROUP 
        FROM SNMPv2-CONF
    experimental
        FROM SNMPv2-SMI;

-- =============================================================================
-- MIB Identity
-- =============================================================================

autoDiscoveryMIB MODULE-IDENTITY
    LAST-UPDATED "202510240000Z"
    ORGANIZATION "Projetos de Gerenciamento de Redes"
    CONTACT-INFO
        "E-mail: andre.renner@acad.ufsm.br
         Autor: Andre Renner(desenvolvedor do software)"
    DESCRIPTION
        "MIB para monitorar e controlar o software de Autodescoberta de Rede.
         Fornece status, controle de scan e uma tabela dos dispositivos descobertos.
         
         Funcionalidades:
         - Descoberta via ARP e validacao por Ping com captura de TTL
         - Scan de portas TCP para identificacao de servicos
         - Classificacao hierarquica de papeis (Gateway > Portas+Fabricante > TTL > SNMP)
         - Suporte para dispositivos unresponsive (detectados via ARP mas sem ping)
         - Modo silencioso para controle de verbosidade
         - Identificacao de fabricantes via OUI (MAC address)"
    REVISION "202510240000Z"
    DESCRIPTION
        "Versao 2.0 - Adiciona suporte para:
         - Status 'unresponsive' para dispositivos detectados mas sem resposta
         - Campo TTL capturado do ping
         - Lista de portas TCP abertas
         - Nome SNMP do dispositivo
         - Papeis refinados: Switch Gerenciavel, Access Point, Servidor Windows, Servidor Web
         - Controle de modo silencioso"
    REVISION "202510050000Z"
    DESCRIPTION
        "Versao inicial da MIB."
    ::= { experimental 9999 }

-- =============================================================================
-- OID Tree Structure
-- =============================================================================

autoDiscoveryObjects       OBJECT IDENTIFIER ::= { autoDiscoveryMIB 1 }
autoDiscoveryConformance OBJECT IDENTIFIER ::= { autoDiscoveryMIB 2 } 

-- =============================================================================
-- Grupo de Objetos Escalares (Controle e Status)
-- =============================================================================

discoveryControlGroup OBJECT IDENTIFIER ::= { autoDiscoveryObjects 1 }
discoveryStatusGroup  OBJECT IDENTIFIER ::= { autoDiscoveryObjects 2 }

targetNetwork OBJECT-TYPE
    SYNTAX      DisplayString (SIZE (0..255))
    MAX-ACCESS  read-write
    STATUS      current
    DESCRIPTION
        "A rede a ser escaneada no formato CIDR (ex: 192.168.1.0/24).
         Se uma string vazia for escrita, o software tentara a deteccao automatica."
    ::= { discoveryControlGroup 1 }

forceScanTrigger OBJECT-TYPE
    SYNTAX      Integer32 (0..1)  -- MUDANÇA: Permitir 0 e 1
    MAX-ACCESS  read-write      -- MUDANÇA: Correto para SMIv2
    STATUS      current
    DESCRIPTION
        "Um gatilho para forcar uma nova varredura da rede imediatamente.
         Escrever o valor '1' neste objeto inicia o processo. 
         A leitura deste objeto sempre retornara '0', indicando
         que o agente esta pronto para um novo gatilho."
    ::= { discoveryControlGroup 2 }
    
silentMode OBJECT-TYPE
    SYNTAX      INTEGER {
                    disabled(0),
                    enabled(1)
                }
    MAX-ACCESS  read-write
    STATUS      current
    DESCRIPTION
        "Controla o modo silencioso do orquestrador.
         disabled(0): Exibe mensagens de status detalhadas durante os scans.
         enabled(1): Oculta mensagens de status para terminal mais limpo.
         Valor padrao: disabled(0)."
    ::= { discoveryControlGroup 3 }

nextScanInSeconds OBJECT-TYPE
    SYNTAX      Gauge32
    MAX-ACCESS  read-only
    STATUS      current
    DESCRIPTION
        "O tempo restante, em segundos, para a proxima varredura automatica.
         Este valor e um medidor (gauge) do estado atual."
    ::= { discoveryStatusGroup 1 }

scansPerformedTotal OBJECT-TYPE
    SYNTAX      Counter32
    MAX-ACCESS  read-only
    STATUS      current
    DESCRIPTION
        "Um contador do numero total de varreduras de rede realizadas
         desde que o software foi iniciado."
    ::= { discoveryStatusGroup 2 }

lastScanDeviceCount OBJECT-TYPE
    SYNTAX      Gauge32
    MAX-ACCESS  read-only
    STATUS      current
    DESCRIPTION
        "O numero de dispositivos encontrados no ultimo scan realizado.
         Este valor e atualizado a cada nova varredura completa."
    ::= { discoveryStatusGroup 3 }

-- =============================================================================
-- Tabela de Dispositivos Descobertos
-- =============================================================================

discoveredDevices OBJECT IDENTIFIER ::= { autoDiscoveryObjects 3 }

deviceTable OBJECT-TYPE
    SYNTAX      SEQUENCE OF DeviceEntry
    MAX-ACCESS  not-accessible
    STATUS      current
    DESCRIPTION
        "Uma tabela contendo os dispositivos encontrados na ultima varredura da rede."
    ::= { discoveredDevices 1 }

deviceEntry OBJECT-TYPE
    SYNTAX      DeviceEntry
    MAX-ACCESS  not-accessible
    STATUS      current
    DESCRIPTION
        "Uma entrada (linha) na tabela de dispositivos, contendo informacoes
         sobre um unico dispositivo descoberto."
    INDEX   { deviceIndex }
    ::= { deviceTable 1 }

DeviceEntry ::= SEQUENCE {
    deviceIndex             Integer32,
    deviceIpAddress         IpAddress,
    deviceMacAddress        DisplayString,
    deviceStatus            INTEGER,
    deviceManufacturer      DisplayString,
    deviceRole              DisplayString,
    deviceFirstSeen         TimeTicks,
    deviceTTL               Integer32,
    deviceSNMPName          DisplayString,
    deviceOpenPorts         DisplayString
}

deviceIndex OBJECT-TYPE
    SYNTAX      Integer32 (1..65535)
    MAX-ACCESS  not-accessible 
    STATUS      current
    DESCRIPTION "Um indice unico para cada linha nesta tabela."
    ::= { deviceEntry 1 }

deviceIpAddress OBJECT-TYPE
    SYNTAX      IpAddress
    MAX-ACCESS  read-only
    STATUS      current
    DESCRIPTION "O endereco IP do dispositivo descoberto."
    ::= { deviceEntry 2 }

deviceMacAddress OBJECT-TYPE
    SYNTAX      DisplayString
    MAX-ACCESS  read-only
    STATUS      current
    DESCRIPTION "O endereco MAC do dispositivo descoberto."
    ::= { deviceEntry 3 }

deviceStatus OBJECT-TYPE
    SYNTAX      INTEGER {
                    online(1),
                    offline(2),
                    unresponsive(3)
                }
    MAX-ACCESS  read-only
    STATUS      current
    DESCRIPTION "O status do dispositivo:
                 online(1): Dispositivo respondeu ao ping e esta acessivel
                 offline(2): Dispositivo nao foi detectado no scan ARP
                 unresponsive(3): Detectado via ARP mas nao responde ao ping (possivelmente firewall)"
    ::= { deviceEntry 4 }

deviceManufacturer OBJECT-TYPE
    SYNTAX      DisplayString
    MAX-ACCESS  read-only
    STATUS      current
    DESCRIPTION "O fabricante do dispositivo, inferido a partir do endereco MAC."
    ::= { deviceEntry 5 }

deviceRole OBJECT-TYPE
    SYNTAX      DisplayString
    MAX-ACCESS  read-only
    STATUS      current
    DESCRIPTION "O papel inferido do dispositivo atraves de classificacao hierarquica:
                 - Roteador: Gateway padrao ou TTL <= 64 ou ipForwarding=1 (SNMP)
                 - Switch Gerenciavel: Portas 22/23 + fabricante de rede (Cisco/Ubiquiti/Palo Alto)
                 - Access Point: Portas 80/443 + fabricante Ubiquiti
                 - Servidor Windows: Porta 3389 (RDP) aberta
                 - Servidor Web: Portas 80/443 abertas
                 - Host: TTL > 64 ou classificacao padrao
                 
                 Hierarquia: Gateway > Portas+Fabricante > TTL > SNMP"
    ::= { deviceEntry 6 }

deviceFirstSeen OBJECT-TYPE
    SYNTAX      TimeTicks
    MAX-ACCESS  read-only
    STATUS      current
    DESCRIPTION "O tempo (em centesimos de segundo) desde que o software foi iniciado
                 ate a primeira vez que este dispositivo foi visto."
    ::= { deviceEntry 7 }

deviceTTL OBJECT-TYPE
    SYNTAX      Integer32 (0..255)
    MAX-ACCESS  read-only
    STATUS      current
    DESCRIPTION "O valor TTL (Time To Live) capturado da resposta ICMP ping.
                 Valores tipicos:
                 - 64: Linux/Unix (comum em roteadores e switches)
                 - 128: Windows (comum em estacoes de trabalho)
                 - 255: Cisco/equipamentos de rede
                 - 0: Nao disponivel (dispositivo unresponsive)"
    ::= { deviceEntry 8 }

deviceSNMPName OBJECT-TYPE
    SYNTAX      DisplayString
    MAX-ACCESS  read-only
    STATUS      current
    DESCRIPTION "O nome do sistema obtido via SNMP (sysName.0).
                 String vazia se SNMP nao estiver disponivel ou configurado."
    ::= { deviceEntry 9 }

deviceOpenPorts OBJECT-TYPE
    SYNTAX      DisplayString
    MAX-ACCESS  read-only
    STATUS      current
    DESCRIPTION "Lista de portas TCP abertas encontradas no scan de portas,
                 separadas por virgula (ex: '22,80,443').
                 String vazia se nenhuma porta estiver aberta ou dispositivo offline.
                 Portas escaneadas: 21(FTP), 22(SSH), 23(Telnet), 80(HTTP), 
                 443(HTTPS), 3389(RDP), 5900(VNC), 8080(HTTP-Alt)"
    ::= { deviceEntry 10 }

-- =============================================================================
-- Conformance Information
-- =============================================================================

autoDiscoveryMIBCompliances OBJECT IDENTIFIER ::= { autoDiscoveryConformance 1 }
autoDiscoveryMIBGroups      OBJECT IDENTIFIER ::= { autoDiscoveryConformance 2 }

-- Grupo de objetos escalares (status e controle)
discoveryScalarGroup OBJECT-GROUP
    OBJECTS {
        targetNetwork,
        forceScanTrigger,
        silentMode,
        nextScanInSeconds,
        scansPerformedTotal,
        lastScanDeviceCount
    }
    STATUS  current
    DESCRIPTION
        "Grupo de objetos escalares para controlar e monitorar o software de descoberta."
    ::= { autoDiscoveryMIBGroups 1 }

-- Grupo de objetos da tabela de dispositivos
discoveryDeviceTableGroup OBJECT-GROUP
    OBJECTS {
        deviceIpAddress,
        deviceMacAddress,
        deviceStatus,
        deviceManufacturer,
        deviceRole,
        deviceFirstSeen,
        deviceTTL,
        deviceSNMPName,
        deviceOpenPorts
    }
    STATUS  current
    DESCRIPTION
        "Grupo de objetos que representam os dados de cada dispositivo na tabela de descoberta.
         Inclui informacoes de rede (IP, MAC), status de conectividade, papel inferido,
         fabricante, TTL, nome SNMP e portas abertas."
    ::= { autoDiscoveryMIBGroups 2 }

-- Declaracao de conformidade
autoDiscoveryMIBCompliance MODULE-COMPLIANCE
    STATUS  current
    DESCRIPTION
        "A declaracao de conformidade para agentes que implementam a AUTO-DISCOVERY-MIB."
    MODULE  -- this module
        MANDATORY-GROUPS {
            discoveryScalarGroup,
            discoveryDeviceTableGroup
        }
    ::= { autoDiscoveryMIBCompliances 1 }

END
